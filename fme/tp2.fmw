FME workspace tp2.fmw

Parameters:
- SourceDataset_SHAPEFILE = C:\Users\Farnoosh\Desktop\geo7630\tp2\fme\census_sections\lct_000b21a_e.shp   # Source Esri Shapefile(s)
- SourceDataset_CSV2 = C:\Users\Farnoosh\Desktop\geo7630\tp2\fme\income.csv   # Source CSV (Comma Separated Value) File(s)
- SourceDataset_SHAPEFILE_3 = C:\Users\Farnoosh\Desktop\geo7630\tp2\fme\quartierreferencehabitation\QuartierReferenceHabitation.shp   # Source Esri Shapefile(s)
- DestDataset_SHAPEFILE = C:\Users\Farnoosh\Desktop\geo7630\tp2\fme   # Destination Esri Shapefile Folder
- SourceDataset_SHAPEFILE_5 = C:\Users\Farnoosh\Desktop\geo7630\tp2\fme\actes-criminels\actes-criminels.shp   # Source Esri Shapefile(s)
- DestDataset_PNGRASTER = C:\Users\Farnoosh\Desktop\geo7630\tp2   # Destination PNG (Portable Network Graphics) Folder

Readers:
- SHAPEFILE_1: SHAPEFILE from $(SourceDataset_SHAPEFILE)
- CSV2_1: CSV2 from $(SourceDataset_CSV2)
- SHAPEFILE_2: SHAPEFILE from $(SourceDataset_SHAPEFILE_3)
- SHAPEFILE_4: SHAPEFILE from $(SourceDataset_SHAPEFILE_5)

Writers:
- SHAPEFILE_3: SHAPEFILE to $(DestDataset_SHAPEFILE)
- PNGRASTER_1: PNGRASTER to $(DestDataset_PNGRASTER)

Junction
    -> SpatialFilter_2 [Filter]
    -> FeatureJoiner_2 [LEFT]
    -> SpatialFilter_3 [Filter]
FeatureJoiner_3
    ATTR_CONFLICT_RES = Prefer Left
    GEOMETRY_HANDLING = Prefer Left
    JOIN_KEYS = CTNAME CTNAME AUTO
    JOIN_MODE = Inner
    JOINED -> FeatureJoiner_2 [RIGHT]
Sections_with_crimes (writer SHAPEFILE_3)
    attributes: NUM_CRIMES varchar(200), CTNAME varchar(7), INC_AVG_BT float, BELOW_ABOV varchar(200), N_CRIME_19 number(20,0), N_CRIME_20 number(20,0)
crime_chart (writer PNGRASTER_1)

Bookmark: COUNT NUMBER OF CRIMES GROUPED BY CENSUS SECTION NUMBER
Note: criminal acts - POINTS
actes-criminels (reader SHAPEFILE_4)
    attributes: CATEGORIE varchar(80), DATE varchar(80), QUART varchar(80), PDQ double, X double, Y double, LONGITUDE double, LATITUDE double
    -> Reprojector_2
Reprojector_2
    DEST = EPSG:3857
    INTERPOLATION_TYPE_NAME = Nearest Neighbor
    RASTER_CELL_SIZE = Preserve Cells
    RASTER_TOLERANCE = 0.0
    REPROJECTED -> Tester_4
    REPROJECTED -> Tester_5
Tester_5
    BOOL_OP = OR
    TEST_CLAUSE = CASE_INSENSITIVE_TEST @Value(DATE) CONTAINS 2019
    TEST_MODE = CASE_INSENSITIVE_TEST
    PASSED -> SpatialFilter_3 [Candidate]
Tester_4
    BOOL_OP = OR
    TEST_CLAUSE = CASE_INSENSITIVE_TEST @Value(DATE) CONTAINS 2020
    TEST_MODE = CASE_INSENSITIVE_TEST
    PASSED -> SpatialFilter_2 [Candidate]
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS CONTAINS
    USE_BOUNDING_BOX = No
    PASSED -> StatisticsCalculator_3
StatisticsCalculator_3
    CALCULATION_MODE = NUMERIC
    FEAT_STATS = CTNAME,NUMERIC_MODE,,,COUNT,,,,,,,,,,
    GROUP_BY = CTNAME
    SUMMARY -> AttributeRenamer_3
AttributeRenamer_3
    ATTR_TABLE = RENAME_SET_DEFAULT CTNAME.total_count > N_CRIME_19
    MISSING_INPUT_ATTRS = REMOVE
    -> FeatureJoiner_3 [LEFT]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS CONTAINS
    USE_BOUNDING_BOX = No
    PASSED -> StatisticsCalculator
StatisticsCalculator
    CALCULATION_MODE = NUMERIC
    FEAT_STATS = CTNAME,NUMERIC_MODE,,,COUNT,,,,,,,,,,
    GROUP_BY = CTNAME
    SUMMARY -> AttributeRenamer_4
AttributeRenamer_4
    ATTR_TABLE = RENAME_SET_DEFAULT CTNAME.total_count > N_CRIME_20
    MISSING_INPUT_ATTRS = REMOVE
    -> FeatureJoiner_3 [RIGHT]

Bookmark: MERGE CENSUS DATA WITH INCOME DATA
Note: Income data
CSV (reader CSV2_1)
    attributes: col0 string, col1 real32, col2 real32, col3 real32, col4 real32
    -> Reprojector_3
Reprojector_3
    DEST = EPSG:3857
    INTERPOLATION_TYPE_NAME = Nearest Neighbor
    RASTER_CELL_SIZE = Preserve Cells
    RASTER_TOLERANCE = 0.0
    REPROJECTED -> AttributeRenamer
AttributeRenamer
    ATTR_TABLE:
      RENAME_SET_DEFAULT col0 > CTNAME
      RENAME_SET_DEFAULT col1 > INC_AVG_BT
      RENAME_SET_DEFAULT col2 > INC_MD_BT
      RENAME_SET_DEFAULT col3 > INC_AVG_AT
      RENAME_SET_DEFAULT col4 > INC_MD_AT
    MISSING_INPUT_ATTRS = REMOVE
    -> FeatureJoiner [RIGHT]
Note: Census sections
lct_000b21a_e (reader SHAPEFILE_1)
    attributes: CTUID varchar(10), DGUID varchar(21), CTNAME varchar(7), LANDAREA double, PRUID varchar(2)
    -> Reprojector_4
Note: Montreal neighbourhoods
QuartierReferenceHabitation (reader SHAPEFILE_2)
    attributes: no_qr varchar(254), nom_qr varchar(254), no_arr varchar(2), nom_arr varchar(100), nom_mun varchar(100)
    -> Reprojector_5
Reprojector_5
    DEST = EPSG:3857
    INTERPOLATION_TYPE_NAME = Nearest Neighbor
    RASTER_CELL_SIZE = Preserve Cells
    RASTER_TOLERANCE = 0.0
    REPROJECTED -> Dissolver
FeatureJoiner
    ATTR_CONFLICT_RES = Prefer Left
    GEOMETRY_HANDLING = Prefer Left
    JOIN_KEYS = CTNAME CTNAME AUTO
    JOIN_MODE = Inner
    JOINED -> Junction
    UNJOINED_LEFT -> Junction

Bookmark: REMOVE UNWANTED CENSUS SECTIONS
Reprojector_4
    DEST = EPSG:3857
    INTERPOLATION_TYPE_NAME = Nearest Neighbor
    RASTER_CELL_SIZE = Preserve Cells
    RASTER_TOLERANCE = 0.0
    REPROJECTED -> SpatialFilter [Candidate]
Dissolver
    ACCUM_INPUT_ATTRS = Use Attributes From One Feature
    CLEANING_TOLERANCE = Automatic
    CONNECT_Z_MODE = First Wins
    DEAGGREGATE_INPUT = Yes
    AREA -> Reprojector
Reprojector
    DEST = EPSG:4326
    INTERPOLATION_TYPE_NAME = Nearest Neighbor
    RASTER_CELL_SIZE = Preserve Cells
    RASTER_TOLERANCE = 0.0
    REPROJECTED -> SpatialFilter [Filter]
SpatialFilter
    AGGREGATE_HANDLING = Yes
    BASE_TYPE = Multiple Filters
    CURVE_BOUNDARY_RULE_PARAM = Default Rule
    PASS_CRITERIA = Pass Against One Filter
    PREDICATES = INTERSECTS
    USE_BOUNDING_BOX = No
    PASSED -> Tester
Tester
    BOOL_OP = OR
    TEST_CLAUSE = TEST @Value(CTNAME) != 0863.02
    TEST_MODE = TEST
    PASSED -> FeatureJoiner [LEFT]

Bookmark: JOIN CRIME NUMBERS WITH POLYGONAL DATA
FeatureJoiner_2
    ATTR_CONFLICT_RES = Prefer Left
    GEOMETRY_HANDLING = Prefer Left
    JOIN_KEYS = CTNAME CTNAME AUTO
    JOIN_MODE = Inner
    JOINED -> Tester_2

Bookmark: ADD BELOW OR ABOVE AVERAGE ATTRIBUTE
Tester_2
    BOOL_OP = OR
    TEST_CLAUSE = TEST INC_AVG_BT ATTRIBUTE_HAS_A_VALUE ""
    TEST_MODE = TEST
    PASSED -> StatisticsCalculator_2
    FAILED -> AttributeKeeper
StatisticsCalculator_2
    CALCULATION_MODE = NUMERIC
    FEAT_STATS = INC_AVG_BT,NUMERIC_MODE,,,COUNT,SUM,,,,,,,,,
    COMPLETE -> AttributeCreator
AttributeCreator
    ATTR_TABLE = SET_TO BELOW_ABOVE
    -> AttributeKeeper

Bookmark: CLEAN ATTRIBUTES
AttributeKeeper
    CREATE_BULK_MODE_FEATURES = NO
    KEEP_ATTRS = CTNAME,INC_AVG_BT,BELOW_ABOVE,N_CRIME_19,N_CRIME_20
    -> AttributeRenamer_2
AttributeRenamer_2
    ATTR_TABLE = RENAME_SET_DEFAULT CTNAME.total_count > NUM_CRIMES
    MISSING_INPUT_ATTRS = REMOVE
    -> AttributeManager
AttributeManager
    ATTR_TABLE = SET_TO INC_AVG_BT = @Evaluate(@Value(INC_AVG_BT)*1000)
    -> Sections_with_crimes (writer SHAPEFILE_3)
    -> Tester_3

Bookmark: CREATE CHART WHICH SHOWS CRIME DATA VS INCOME
Tester_3
    BOOL_OP = OR
    TEST_CLAUSE = TEST INC_AVG_BT ATTRIBUTE_HAS_A_VALUE ""
    TEST_MODE = TEST
    PASSED -> ChartGenerator
ChartGenerator
    AXES_FONT = Arial,12
    AXES_LW = 0.5
    BACKGROUND_COLOR = 1,1,1
    CHART_SETUP = XATT;INC_AVG_BT;YATT;N_CRIME_20;EATT;;COLOR;0,0,1;POINT_STYLE;CIRCLE;POINT_SIZE;1.0;TREND_LINE;NO;DISCRETE_X;NO;DISCRETE_Y;NO;FME_CONTROLLER_QUERY_FILE;transformers/dependencies/charter/Scatter.fme;FME_CONTROLLER_CHOICE;Scatter
    CHART_TITLE = Crimes vs Income
    CHART_TYPE = Scatter
    DPI = 300
    INTERPRETATION = RGBA32
    LEGEND = OUR
    LEGEND_FONT = Arial,10
    LEGEND_OPTIONS = YES
    MULTI_DS = NO
    TICKS = T
    TICK_FONT = Arial,10
    TITLE_FONT = Arial,12
    X_INCH = 2.0
    X_LABEL = Income
    X_LABEL_ANGLE = Horizontal (0)
    X_LOG = LIN
    Y_INCH = 2.0
    Y_LABEL = # of crimes
    Y_LABEL_ANGLE = Horizontal (0)
    Y_LOG = LOG
    -> crime_chart (writer PNGRASTER_1)
